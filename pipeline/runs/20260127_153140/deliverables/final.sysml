package RequirementsOnly {
  requirement RQ_001 {
    text = "# Natural-language brief (echoed twice per Sysmlgeneration guidance)
Design a circuit whose LED flickers at 10 Hz ±5% from a 5 V supply; include current limiting and make it sourceable from Mouser.

-- repeat --
Design a circuit whose LED flickers at 10 Hz ±5% from a 5 V supply; include current limiting and make it sourceable from Mouser.

# Instructions to the model (keep in prompt for refine_sysml.py)
- Emit the minimal SysMLv2 that satisfies the brief.
- Avoid redundant packages/properties; be concise.
- Conform to SysIDE; model must pass `syside check`.
- If uncertain, make the best assumption and note it in a comment.";
  }
}
